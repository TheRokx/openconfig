module frinx-saos-if-extension {

  yang-version "1";

  // namespace
  namespace "http://frinx.openconfig.net/yang/interfaces/saos-extension";

  prefix "saos-if-ext";

  // import some basic types
  import frinx-openconfig-interfaces { prefix oc-if; }
  // uniconfig imports
  import network-topology { prefix nt; revision-date "2013-10-21"; }
  import frinx-uniconfig-topology { prefix ut; revision-date "2017-11-21"; }
  import yang-ext { prefix ext; revision-date "2013-07-09"; }

  // meta
  organization "Frinx s.r.o";

  contact
    "support@frinx.io";

  description
    "Set of augments needed to OpenConfig interfaces models,
    containing SAOS specific features.";

  revision "2020-02-05" {
    description
      "Initial release";
    reference "3.1.13";
  }

  grouping saos-if-extension-config {
    leaf physical-type {
      type enumeration {
        enum default {
          description
            "type default";
        }
        enum rj45 {
          description
            "type rj45";
        }
        enum sfp {
          description
            "type sfp";
        }
      }
    }

    leaf acceptable-frame-type {
      type enumeration {
        enum all {
          description
            "type all";
        }
        enum tagged-only {
          description
            "tagged-only";
        }
        enum untagged-only {
          description
            "untagged-only";
        }
      }
    }

    leaf vs-ingress-filter {
      type boolean;
      description
        "Set virtual switch ingress filter.";
    }

    leaf vlan-ethertype-policy {
      type enumeration {
        enum all {
          description
            "type all";
        }
        enum vlan-tpid {
          description
            "type vlan-tpid";
        }
      }
    }

    leaf ingress-to-egress-qmap {
      type enumeration {
        enum NNI-NNI {
          description
            "NNI-NNI";
        }
        enum Default-RCOS {
          description
            "Default-RCOS";
        }
      }
    }

    leaf forward-unlearned {
      type boolean;
      description
        "The Forward-Unlearned option allows for the forwarding or dropping of frames
         containing unknown, that is, unlearned, source MAC addresses when the
         SAC limit has been reached on a port. The Forward-Unlearned option
         is turned on by default for each port.";
    }

    leaf max-dynamic-macs {
      type uint16;
      description
        "The maximum number of allowed dynamic MAC address";
    }
  }

  grouping saos-if-extension-l2-cft {
    description "Reference to l2-cft profile.";

    container cft-profile {
      description "Containter for l2-cft profile.";

      container config {
        description "Configuration parameters for l2-cft profile.";

        leaf name {
          type string;
          description "Name of l2-cft profile.";
        }

        leaf enabled {
          type boolean;
          description "Port enable/disable.";
        }
      }
    }
  }

  grouping saos-if-extension-pm-instances {

    container pm-instances {
      description "Container for pm-instances.";

      list pm-instance {
        key "name";

        description "pm-instance.";

        leaf name {
          type leafref {
            path "../config/name";
          }
          description
            "Name of pm-instance.";
        }

        container config {
          description
            "Config container of pm-instance.";

          leaf name {
            type string;
              description
                "Name of pm-instance.";
          }

          leaf bin-count {
            type string;
            description "Number of history bins.";
          }
        }
      }
    }
  }

  // augment statements

  augment "/oc-if:interfaces/oc-if:interface/oc-if:config" {
    description "Adds SAOS specific configuration to interfaces model";
    ext:augment-identifier "if-saos-aug";

    uses saos-if-extension-config;
  }

  augment "/oc-if:interfaces/oc-if:interface" {
    description "Adds SAOS specific configuration to interfaces model";
    ext:augment-identifier "saos-6-if-cft-aug";

    uses saos-if-extension-l2-cft;
  }

  augment "/oc-if:interfaces/oc-if:interface/oc-if:subinterfaces/oc-if:subinterface" {
    description "Adds SAOS specific configuration to interfaces model";
    ext:augment-identifier "saos-8-pm-instance-aug";

    uses saos-if-extension-pm-instances;
  }

  // uniconfig augmentations

  augment "/nt:network-topology/nt:topology/nt:node/ut:configuration/oc-if:interfaces/oc-if:interface/oc-if:config" {
    description "Adds SAOS specific configuration to interfaces model";

    uses saos-if-extension-config;
  }

  augment "/nt:network-topology/nt:topology/nt:node/ut:configuration/oc-if:interfaces/oc-if:interface" {
    description "Adds SAOS specific configuration to interfaces model";

    uses saos-if-extension-l2-cft;
  }

  augment "/nt:network-topology/nt:topology/nt:node/ut:configuration/oc-if:interfaces/oc-if:interface/" +
    "oc-if:subinterfaces/oc-if:subinterface" {
    description "Adds SAOS specific configuration to interfaces model";

    uses saos-if-extension-pm-instances;
  }
}
