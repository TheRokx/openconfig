module frinx-saos-vs-extension {

  yang-version "1";

  // namespace
  namespace "http://frinx.openconfig.net/yang/saos/extension";

  prefix "saos-vs-ext";

  // import some basic types
  import frinx-openconfig-network-instance { prefix oc-ni; }
  // uniconfig imports
  import network-topology { prefix nt; revision-date "2013-10-21"; }
  import frinx-uniconfig-topology { prefix ut; revision-date "2017-11-21"; }
  import yang-ext { prefix ext; revision-date "2013-07-09"; }

  // meta
  organization "Frinx s.r.o";

  contact
    "support@frinx.io";

  description
    "Set of augments needed to OpenConfig interfaces models,
    containing SAOS specific features.";

  revision "2020-02-10" {
    description
      "Initial release";
    reference "3.1.14";
  }

  grouping saos-vs-extension {
    leaf encap-cos-policy {
      type enumeration {
        enum fixed {
          description
            "default";
        }
        enum dot1dpri-inherit {
          description
            "dot1dpri-inherit";
        }
        enum ip-prec-inherit {
          description
            "ip-prec-inherit";
        }
        enum phbg-inherit {
          description
            "phbg-inherit";
        }
        enum port-inherit {
          description
            "port-inherit";
        }
        enum vs-inherit {
          description
            "vs-inherit";
        }
      }
    }

    leaf encap-fixed-dot1dpri {
      type uint8;
        description
          "value from 0-7";
    }

    leaf tagged-pvst-l2pt {
      type boolean;
        description
          "Enable/disable tagged-pvst-l2pt for virtual-switch";
    }
  }

  // augment statements
  augment "/oc-ni:network-instances/oc-ni:network-instance/oc-ni:config" {
    description "Adds SAOS specific configuration to network-instance model";
    ext:augment-identifier "vs-saos-aug";
    uses saos-vs-extension;
  }

  // uniconfig augmentations
  augment "/nt:network-topology/nt:topology/nt:node/ut:configuration/oc-ni:network-instances/oc-ni:network-instance/oc-ni:config" {
    description "Adds SAOS specific configuration to network-instance model";
    uses saos-vs-extension;
  }
}
