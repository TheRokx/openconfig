module frinx-dasan-vlan-extension {

  yang-version "1";

  // namespace
  namespace "http://frinx.openconfig.net/yang/vlan/dasan";

  prefix "dasan-vlan-ext";

  // import some basic types
  import frinx-openconfig-network-instance { prefix oc-netinst; }
  // uniconfig imports
  import network-topology { prefix nt; revision-date "2013-10-21"; }
  import frinx-uniconfig-topology { prefix ut; revision-date "2017-11-21"; }

  // meta
  organization "Frinx s.r.o";

  contact
    "support@frinx.io";

  description
    "Set of augments needed to OpenConfig vlan models,
    containing dasan specific features.";

  revision "2018-08-01" {
    description
      "Initial release";
    reference "3.1.6";
  }

  // grouping statements

  grouping dasan-vlan-extension-config {
    leaf eline {
      type boolean;

      // default false;

      description
        "Specify eline for vlan create command.";
    }
  }

  // augment statements

  augment "/oc-netinst:network-instances/oc-netinst:network-instance/oc-netinst:vlans/oc-netinst:vlan/oc-netinst:config" {
    description "Adds dasan specific configuration to vlan config model";

    uses dasan-vlan-extension-config;
  }

  augment "/oc-netinst:network-instances/oc-netinst:network-instance/oc-netinst:vlans/oc-netinst:vlan/oc-netinst:state" {
      description "Adds dasan specific configuration to vlan config model";

      uses dasan-vlan-extension-config;
    }

  // uniconfig augmentations

  augment "/nt:network-topology/nt:topology/nt:node/ut:configuration/"
      + "oc-netinst:network-instances/oc-netinst:network-instance/oc-netinst:vlans/oc-netinst:vlan/oc-netinst:config" {

    description "Adds dasan specific configuration to vlan config model";

    uses dasan-vlan-extension-config;
  }

  augment "/nt:network-topology/nt:topology/nt:node/ut:configuration/"
      + "oc-netinst:network-instances/oc-netinst:network-instance/oc-netinst:vlans/oc-netinst:vlan/oc-netinst:state" {

    description "Adds dasan specific configuration to vlan config model";

    uses dasan-vlan-extension-config;
  }
}
